package VersionMark {
    private import SoftwareItemMetadata::*;

    part def MarkdownFormatter {
        doc /* Converts loaded version records into a consolidated markdown report. */

        metadata info : SoftwareInfo {
            sourceFiles = ("src/DemaConsulting.VersionMark/Publishing/MarkdownFormatter.cs");
            testFiles = ("test/DemaConsulting.VersionMark.Tests/Publishing/MarkdownFormatterTests.cs");
            designFiles = ("docs/design/version-mark/publishing/markdown-formatter.md");
            verificationFiles = ("docs/verification/version-mark/publishing/markdown-formatter.md");
            requirementFiles = ("docs/reqstream/version-mark/publishing/markdown-formatter.yaml");
        }
    }

    // Format takes the loaded VersionInfo records as its input data model.
    dependency MarkdownFormatter to VersionInfo;
}
